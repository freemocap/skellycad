import sys, importlib
from pathlib import Path
here=Path(__file__).resolve().parent
if str(here) not in sys.path:sys.path.insert(0,str(here))
import camera_study
importlib.reload(camera_study)
camera_study.build()
