from pathlib import Path
import sys
root=next(p for p in Path(__file__).resolve().parents if (p/'AGENTS.md').is_file())
sys.path.insert(0,str(root/'designs/eye-tracker'))
from shared.review import open_review
open_review(Path(__file__).parent/'active-model.json')
