from pathlib import Path
import json,hashlib
import FreeCAD as A,FreeCADGui as G,Part,Mesh
R=Path(__file__).resolve().parents[4];S=R/'designs/eye-tracker/mouse/skull-clearance-r18';O=R/'generated/eye-tracker/mouse/skull-clearance-r18';O.mkdir(parents=True,exist_ok=True)
m=json.loads((S.parent/'anatomical-mount-r17/review.json').read_text());src=R/m['native_checkpoint'];assert hashlib.sha256(src.read_bytes()).hexdigest()==m['native_sha256'];sel=json.loads((S.parent/'active-model.json').read_text());assert hashlib.sha256((R/sel['native_checkpoint']).read_bytes()).hexdigest()==sel['native_sha256'];d=A.openDocument(str(src));A.setActiveDocument(d.Name);p=json.loads((S/'placement.json').read_text());D=A.Placement(A.Matrix(*sum(p['transform'],[])));shape=Part.Shape();shape.read(str(S.parent/'anatomical-mount-r17/baseline-baseplate-world.brep'));new=shape.copy();new.Placement=D.multiply(shape.Placement);d.AlignedBaseplate.Shape=new;d.AlignedBaseplate.Label='R18: surface-parallel, raised baseplate';d.AlignedBaseplate.ViewObject.Transparency=15;d.ExistingBaseplate.Visibility=False;d.MountDatum.Visibility=False;d.MountDatumLabel.Visibility=False
h=d.addObject('Part::Feature','RearHoleClearance');h.Shape=new.Faces[34];h.ViewObject.ShapeColor=(1.,.5,.05);h.Label='Rear 2.9 mm screw hole - measured clearance region'
for o in d.Objects:
 if o.TypeId=='App::Annotation':o.Visibility=False
for name in ['NamedLabel13','NamedLabel16']:
 o=d.getObject(name)
 if o:o.Visibility=True
note=d.addObject('App::Annotation','ClearanceSummary');note.LabelText=['Raised 0.75 mm; face follows local skull plane',f"Rear hole clearance >= {p['rear_hole_conservative_clearance_mm']:.2f} mm (mesh bound)"];note.Position=A.Vector(-8,5,1);note.ViewObject.FontSize=13.;note.ViewObject.TextColor=(.1,.3,.6)
d.recompute();d.Label='Mouse baseplate R18 - surface angle and rear clearance';v=G.activeDocument().activeView();v.viewAxonometric();v.fitAll();d.saveAs(str(O/'ET-MOUSE-BASEPLATE-R18.FCStd'))
