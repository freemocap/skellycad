from pathlib import Path
import json,hashlib
import FreeCAD as A,FreeCADGui as G,Mesh,Part
S=Path(__file__).resolve().parent;R=S.parents[3];O=R/'generated/eye-tracker/mouse/landmark-eyes-r04'
m=json.loads((R/'designs/eye-tracker/mouse/named-landmarks-r03/review.json').read_text());src=R/m['native_checkpoint'];assert hashlib.sha256(src.read_bytes()).hexdigest()==m['native_sha256'];d=A.openDocument(str(src));d.Label='Mouse anatomy R04 - landmark frame and fitted eye centers'
r=json.loads((S/'placement.json').read_text());g=d.addObject('App::DocumentObjectGroup','LandmarkFittedEyes');g.Label='Adult eyes - tissue-estimated centers and nominal ambulatory gaze'
for i,row in enumerate(r['eyes'],1):
 for region,color in [('sclera',(.94,.91,.78)),('cornea',(.05,.6,.8))]:
  o=d.addObject('Mesh::Feature',f'FittedEye{i}{region}');o.Mesh=Mesh.Mesh(str(O/(row['eye']+'-'+region+'.stl')));o.ViewObject.ShapeColor=color;o.ViewObject.DisplayMode='Shaded';g.addObject(o)
 c=A.Vector(*row['center_world_mm']);v=A.Vector(*row['axis_world']);o=d.addObject('Part::Feature',f'FittedEye{i}Axis');tip=c+v*5;o.Shape=Part.makeCompound([Part.makeLine(c-v*3,tip),Part.makeLine(tip,tip-v*.6+A.Vector(.2,0,0)),Part.makeLine(tip,tip-v*.6-A.Vector(.2,0,0))]);o.ViewObject.LineColor=(.0,.65,.2) if i==1 else (.85,.1,.6);o.ViewObject.LineWidth=3.;g.addObject(o)
 o.addProperty('App::PropertyVector','EyeCenter');o.EyeCenter=c;o.addProperty('App::PropertyVector','OpticalDirection');o.OpticalDirection=v
frame=d.addObject('App::Part','AcceptedSkullFrame');frame.Label='Accepted landmark frame: origin bregma, X forward, Y left, Z dorsal';B=r['skull_basis_columns'];M=A.Matrix();
for i in range(3):
 for j in range(3):setattr(M,'A'+str(i+1)+str(j+1),B[i][j])
frame.Placement=A.Placement(A.Vector(*r['skull_origin_world_mm']),A.Rotation(M))
for i,(name,color) in enumerate([('Forward',(.9,.1,.1)),('Left',(.1,.7,.1)),('Dorsal',(.1,.3,.9))]):
 o=d.addObject('Part::Feature','Accepted'+name);p=A.Vector();p[i]=3;o.Shape=Part.makeLine(A.Vector(),p);o.ViewObject.LineColor=color;o.ViewObject.LineWidth=3.;frame.addObject(o)
for o in d.NamedReferences.Group:
 if o.TypeId=='App::Annotation':o.LabelText=[o.LabelText[0].rstrip(' *')]
 if hasattr(o,'SourceID'):o.addProperty('App::PropertyString','UserReview');o.UserReview='Visually accepted for this model on 2026-10-14; original source coordinates preserved'
d.DetailedReference.ViewObject.Transparency=35;d.recompute();G.activeDocument().activeView().viewAxonometric();G.activeDocument().activeView().fitAll();d.saveAs(str(O/'ET-MOUSE-LANDMARK-EYES-R04.FCStd'))
