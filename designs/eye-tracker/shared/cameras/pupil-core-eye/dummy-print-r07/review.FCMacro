try:
 import FreeCAD as A, FreeCADGui as G, Part
 from pathlib import Path
 out=Path('C:/Users/jonma/code-stuff/github/freemocap/other/skellycad/generated/eye-tracker/shared/camera-dummy-r07');lensdir=Path('C:/Users/jonma/code-stuff/github/freemocap/other/skellycad/generated/eye-tracker/shared/lens-m5-r05')
 d=A.openDocument(str(out/'CAMERA-DUMMY-R07.FCStd'))
 d.CameraModule.ViewObject.Visibility=True
 for name,color in [('Red_PLA_boards',(1.0,.12,.1)),('Black_PLA_lens',(.16,.16,.18)),('White_PLA_connector_LEDs',(.94,.94,.9)),('Yellow_TPU_ribbon',(1.0,.8,.02))]:
  o=d.getObject(name);o.ViewObject.Visibility=True;o.ViewObject.ShapeColor=color;o.ViewObject.Transparency=0
 axis=d.OpticalAxis;axis.ViewObject.Visibility=True;axis.ViewObject.LineColor=(0.0,.65,.95);axis.ViewObject.LineWidth=3
 d.SensorPlane.ViewObject.Visibility=False
 d.recompute();G.activeDocument().activeView().viewAxonometric();G.activeDocument().activeView().fitAll();G.updateGui();d.save()
 G.activeDocument().activeView().saveImage(str(out/'camera-preview.png'),1600,1000,'White')
 # Standalone accepted lens with the same axis definition, in its local frame.
 l=A.newDocument('LensWithOpticalAxis');l.Label='Lens with optical axis and sensor normal'
 module=l.addObject('App::Part','LensAssembly');module.ViewObject.Visibility=True
 for name,color in [('Housing',(.18,.18,.2)),('ProtrudingLensBarrel',(.08,.08,.09)),('FakeLens',(.28,.31,.35))]:
  s=Part.Shape();s.read(str(lensdir/(name+'.step')));o=l.addObject('Part::Feature',name);o.Shape=s;module.addObject(o);o.ViewObject.ShapeColor=color;o.ViewObject.Visibility=True
 origin=A.Vector(0,0,d.OpticalAxis.Origin.z-d.OpticalAxis.SensorCenter.z)
 a=l.addObject('Part::Feature','OpticalAxis');module.addObject(a)
 a.Shape=Part.makeCompound([Part.makeLine(origin,origin+A.Vector(0,0,9)),Part.makeLine(origin+A.Vector(0,0,9),origin+A.Vector(.45,0,8)),Part.makeLine(origin+A.Vector(0,0,9),origin+A.Vector(-.45,0,8))])
 for name,value in [('Origin',origin),('Direction',A.Vector(0,0,1)),('SensorCenter',A.Vector(0,0,0))]:a.addProperty('App::PropertyVector',name,'Optical datum');setattr(a,name,value)
 a.addProperty('App::PropertyBool','ExportForPrinting').ExportForPrinting=False
 a.ViewObject.LineColor=(0.0,.65,.95);a.ViewObject.LineWidth=3
 f=l.addObject('App::FeaturePython','SensorFrame');module.addObject(f);f.addProperty('App::PropertyPlacement','Placement').Placement=A.Placement()
 A.setActiveDocument(l.Name);l.recompute();G.activeDocument().activeView().viewAxonometric();G.activeDocument().activeView().fitAll();G.updateGui()
 l.saveAs(str(out/'LENS-WITH-OPTICAL-AXIS.FCStd'))
 G.activeDocument().activeView().saveImage(str(out/'lens-axis-preview.png'),1100,1000,'White')
 A.setActiveDocument(d.Name);G.activeDocument().activeView().fitAll();G.updateGui()
 (out/'review-complete.txt').write_text('Complete camera module and standalone lens with optical axis displayed and saved')
except Exception:
 import traceback
 from pathlib import Path
 Path('C:/Users/jonma/code-stuff/github/freemocap/other/skellycad/generated/eye-tracker/shared/camera-dummy-r07/review-error.txt').write_text(traceback.format_exc())
