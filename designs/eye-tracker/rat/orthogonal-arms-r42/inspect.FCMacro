from pathlib import Path
import FreeCAD as A,FreeCADGui as G
from PySide import QtCore
from pivy import coin
R=Path(__file__).resolve().parents[4];O=R/'generated/eye-tracker/rat/orthogonal-arms-r42'
d=A.openDocument(str(O/'04-arms.FCStd'));A.setActiveDocument(d.Name)
for o in d.Objects:o.Visibility=False
for name in ['CentralCarrier','RightUpperSupport','RightLowerSupport','LeftUpperSupport','LeftLowerSupport','RightRetainedSocket','LeftRetainedSocket']:
 o=d.getObject(name);o.Visibility=True;o.ViewObject.ShapeColor=(.9,.65,.2) if name=='CentralCarrier' else (.45,.65,.8)
v=G.activeDocument().activeView();v.viewAxonometric();v.fitAll();v.getCameraNode().nearDistance.setValue(.01);v.getCameraNode().farDistance.setValue(10000);G.updateGui()
def capture():
 v.saveImage(str(O/'unfinished-junctions.png'),1600,1200,'White');d.saveAs(str(O/'R42-work-review.FCStd'))
QtCore.QTimer.singleShot(1500,capture)
