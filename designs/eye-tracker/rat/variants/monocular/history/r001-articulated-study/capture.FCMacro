from pathlib import Path
import FreeCADGui as G
O=Path(__file__).resolve().parents[4]/'generated/eye-tracker/rat/articulated-study-r01'
G.activeDocument().activeView().saveImage(str(O/'comparison.png'),1800,1000,'White')
