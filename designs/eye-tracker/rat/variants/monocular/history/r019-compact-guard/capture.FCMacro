from pathlib import Path
import FreeCADGui as G
G.activeDocument().activeView().saveImage(str(Path(__file__).resolve().parents[4]/'generated/eye-tracker/rat/compact-guard-r19/review.png'),1600,1100,'White')
