# Reuse the live review instead of creating another owner of its save path.
def _open_review():
    from pathlib import Path
    import runpy
    import FreeCAD as App
    root = Path(__file__).resolve().parents[4]
    find_open = runpy.run_path(str(root / 'tools/cad/review_document.py'))['find_open_document']
    if find_open(App, root / 'generated/eye-tracker/rat/bregma-baseplate-r17/ET-RAT-BREGMA-BASEPLATE-R17.FCStd'):
        return
    from pathlib import Path
    import json,hashlib
    import FreeCAD as A,FreeCADGui as G,Part,Mesh
    S=Path(__file__).resolve().parent;R=S.parents[3];O=R/'generated/eye-tracker/rat/bregma-baseplate-r17';p=json.loads((S/'placement.json').read_text());a=json.loads((S.parent/'symmetric-design-r16/review.json').read_text());src=R/a['native_checkpoint'];assert hashlib.sha256(src.read_bytes()).hexdigest()==a['native_sha256'];d=A.openDocument(str(src));A.setActiveDocument(d.Name)
    for obj in d.Objects:
     if obj.TypeId=='App::Annotation' or obj.Name.startswith(('ReferenceLeader','SurfaceReference','DesignMidline')):obj.Visibility=False
    shape=Part.Shape();shape.read(str(S/'source-baseplate.brep'));shape.Placement=A.Placement(A.Matrix(*sum(p['transform'],[]))).multiply(shape.Placement)
    obj=d.addObject('Part::Feature','BregmaBaseplate');obj.Label='Baseplate - rostral tip above bregma, body caudal';obj.Shape=shape;obj.ViewObject.ShapeColor=(.15,.5,.85);obj.ViewObject.Transparency=15
    assert shape.isValid();assert abs(shape.Volume-json.loads((S/'source-geometry.json').read_text())['volume'])<1e-5
    Mesh.Mesh(shape.Faces[34].tessellate(.03)).write(str(O/'rear-hole-wall.stl'))
    for name,pos,color in [('Bregma design reference',p['bregma_design_proxy_mm'],(1.,.15,.1)),('Baseplate rostral tip',p['rostral_tip_design_mm'],(.15,.3,.9))]:
     q=A.Vector(*pos);o=d.addObject('Part::Feature','MountReference');o.Label=name;o.Shape=Part.makeSphere(.25,q);o.ViewObject.ShapeColor=color
     label=d.addObject('App::Annotation','MountLabel');label.LabelText=[name];label.Position=q+A.Vector(2,8,2);label.ViewObject.TextColor=color;label.ViewObject.FontSize=14
    line=d.addObject('Part::Feature','TipProjection');line.Shape=Part.makeLine(A.Vector(*p['bregma_design_proxy_mm']),A.Vector(*p['rostral_tip_design_mm']));line.ViewObject.LineColor=(.9,.2,.1);line.ViewObject.DrawStyle='Dashed'
    d.Label='Rat R17 - caudal baseplate with tip at bregma';d.recompute();G.activeDocument().activeView().viewAxonometric();G.activeDocument().activeView().fitAll();d.saveAs(str(O/'ET-RAT-BREGMA-BASEPLATE-R17.FCStd'));G.updateGui()

_open_review()
